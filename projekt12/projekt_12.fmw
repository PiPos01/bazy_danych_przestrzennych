FME workspace projekt_12.fmw

Parameters:
- SourceDataset_SHAPEFILE = ""$(FME_MF_DIR)T2019_KAR_GERMANY\T2019_KAR_POI_TABLE.shp" "$(FME_MF_DIR)T2019_KAR_GERMANY\T2019_KAR_STREET_NODE.shp" "$(FME_MF_DIR)T2019_KAR_GERMANY\T2019_KAR_STREETS.shp""   # Source Esri Shapefile(s)
- SourceDataset_CSV2_3 = $(FME_MF_DIR)dane.csv   # Source CSV (Comma Separated Value) File(s)
- SourceDataset_CSV2 = $(FME_MF_DIR)dane.csv   # Source CSV (Comma Separated Value) File(s)
- SourceDataset_SHAPEFILE_3 = ""$(FME_MF_DIR)T2019_KAR_GERMANY\T2019_KAR_POI_TABLE.shp" "$(FME_MF_DIR)T2019_KAR_GERMANY\T2019_KAR_STREET_NODE.shp" "$(FME_MF_DIR)T2019_KAR_GERMANY\T2019_KAR_STREETS.shp""   # Source Esri Shapefile(s)
- DestDataset_GEODATABASE_FILE_3 = $(FME_MF_DIR)bez_kosztów.gdb   # File Geodatabase
- DestDataset_GEODATABASE_FILE = $(FME_MF_DIR)z_kosztami.gdb   # File Geodatabase

Readers:
- SHAPEFILE_1: SHAPEFILE from $(SourceDataset_SHAPEFILE)
- CSV2_2: CSV2 from $(SourceDataset_CSV2_3)
- CSV2_1: CSV2 from $(SourceDataset_CSV2)
- SHAPEFILE_2: SHAPEFILE from $(SourceDataset_SHAPEFILE_3)

Writers:
- GEODATABASE_FILE_1: GEODATABASE_FILE to $(DestDataset_GEODATABASE_FILE)
- GEODATABASE_FILE_2: GEODATABASE_FILE to $(DestDataset_GEODATABASE_FILE_3)

T2019_KAR_STREET_NODE (reader SHAPEFILE_2)
    attributes: NODE_ID long, LINK_ID long, POINT_NUM long, Z_LEVEL long, INTERSECT varchar(1), LAT number(31,15), LON number(31,15)
    -> Reprojector_2
CSV (reader CSV2_1)
    attributes: col0 real32, col1 real32
    -> LineBuilder_2
LineBuilder_2
    ACCUM_INPUT_ATTRS_LOOKUP = One
    REMOVE_DUPLICATES_LOOKUP = NO
    ACCUM_INPUT_ATTRS = Use Attributes From One Feature
    REMOVE_DUPLICATES = No
    LINE -> Reprojector_2
T2019_KAR_POI_TABLE (reader SHAPEFILE_2)
    attributes: POI_ID long, LINK_ID long, TYPE varchar(250), POI_NAME varchar(250), ST_NAME varchar(250), LAT number(31,15), LON number(31,15)
    -> Reprojector_2
T2019_KAR_STREETS (reader SHAPEFILE_2)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_2
Reprojector_2
    DEST = EPSG:3068
    INTERPOLATION_TYPE = NearestNeighbor
    RASTER_CELL_SIZE = PreserveCells
    RASTER_TOLERANCE = 0.0
    SOURCE = EPSG:4326
    REPROJECTED -> TestFilter_2
TestFilter_2
    DEFAULT_VALUE = <UNFILTERED>
    PASSED_TEST_GROUP_OUTPUT = ALL
    TEST_LIST = "BOOL_OP,OR,COMPOSITE_TEST,""""""1"""""",TEST_CLAUSE,TEST @Value(fme_feature_type) = T2019_KAR_STREETS",@Value(fme_feature_type) = T2019_KAR_STREETS,"BOOL_OP,OR,COMPOSITE_TEST,""""""1"""""",TEST_CLAUSE,TEST @Value(fme_feature_type) = T2019_KAR_POI_TABLE",@Value(fme_feature_type) = T2019_KAR_POI_TABLE,"BOOL_OP,OR,COMPOSITE_TEST,""""""1"""""",TEST_CLAUSE,TEST @Value(fme_feature_type) = T2019_KAR_STREET_NODE",@Value(fme_feature_type) = T2019_KAR_STREET_NODE,"BOOL_OP,OR,COMPOSITE_TEST,""""""1"""""",TEST_CLAUSE,TEST @Value(fme_feature_type) = CSV",@Value(fme_feature_type) = CSV
    @Value(fme_feature_type) = T2019_KAR_STREETS -> Tester
    @Value(fme_feature_type) = T2019_KAR_POI_TABLE -> Clipper [CANDIDATE]
    @Value(fme_feature_type) = T2019_KAR_STREET_NODE -> SpatialFilter_2 [Candidate]
    @Value(fme_feature_type) = CSV -> ShortestPathFinder [FROM-TO]
Tester
    BOOL_OP = OR
    TEST_CLAUSE:
      TEST @Value(DIR_TRAVEL) = F
      TEST @Value(DIR_TRAVEL) = T
    TEST_MODE = TEST
    PASSED -> AttributeCreator
    FAILED -> AttributeCreator_2
AttributeCreator
    ATTR_TABLE:
      SET_TO ForwardCost (varchar(200)) = FME_CONDITIONAL:DEFAULT_VALUE'9999'BOOL_OP;OR;COMPOSITE_TEST;1;TEST @Value(DIR_TRAVEL) = F'1'FME_NUM_CONDITIONS2___
      SET_TO ReverseCost (varchar(200)) = FME_CONDITIONAL:DEFAULT_VALUE'9999'BOOL_OP;OR;COMPOSITE_TEST;1;TEST @Value(DIR_TRAVEL) = T'1'FME_NUM_CONDITIONS2___
    INPUT_PORT_CONNECTED = CONNECTED
    -> ShortestPathFinder [NETWORK]
AttributeCreator_2
    ATTR_TABLE:
      SET_TO ForwardCost (uint8) = 1
      SET_TO ReverseCost (uint8) = 1
    INPUT_PORT_CONNECTED = CONNECTED
    -> ShortestPathFinder [NETWORK]
ShortestPathFinder
    ALLOW_UTURNS = No
    REORDER_MODE = NONE
    SNAP_POINTS = Yes
    SNAP_TOLERANCE = 200
    THREE_D = No
    WEIGHT_ATTR_1 = @Value(ForwardCost)
    WEIGHT_ATTR_2 = @Value(ReverseCost)
    WEIGHT_ATTR_CHOICE = BY_TWO_ATTRIBUTES
    PATH -> Bufferer
    PATH -> SpatialFilter_2 [Filter]
    PATH -> LengthCalculator
Bufferer
    ANGLE = 22.5
    CAP_STYLE_LOOKUP = CAP_ARC
    CORNER_STYLE_LOOKUP = JOIN_ARC
    MODE = AREA
    OFFSET = 5
    OFFSET_UNITS = NONE
    PRECISION = APPROX
    CAP_STYLE = Arc
    CORNER_STYLE = Arc
    BUFFERED -> Clipper [CLIPPER]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> FeatureWriter_2 [Inside]
FeatureWriter_2
    CONFIG_PARAMETERS = ESCAPE_COMMAS_IN_FTP_FORMAT_PARAMETERS,no
    DATASET = $(FME_MF_DIR_ENCODED)z_kosztami.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    GEOJSON_WRITE_FEATURE_IDS = Yes
    GEOJSON_WRITE_NESTED = YES
    TOTAL_FEATURES_WRITTEN_ATTR = _total_features_written
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> z_kosztami (writer GEODATABASE_FILE_1)
LengthCalculator
    DIM = 2
    LEN_ATTR = _length
    MULT = 1
    -> z_kosztami (writer GEODATABASE_FILE_1)
z_kosztami (writer GEODATABASE_FILE_1)
    attributes: POI_ID integer, LINK_ID integer, TYPE char(250), POI_NAME char(250), ST_NAME char(250), LAT double(31,15), LON double(31,15), NODE_ID integer, POINT_NUM integer, Z_LEVEL integer, INTERSECT char(1), REF_IN_ID integer, NREF_IN_ID integer, FUNC_CLASS char(1), SPEED_CAT char(1), FR_SPEED_L integer, TO_SPEED_L integer, DIR_TRAVEL char(1), col0 float, col1 float, _total_cost char(2048), _predicate char(2048), _length double
T2019_KAR_POI_TABLE (reader SHAPEFILE_1)
    attributes: POI_ID long, LINK_ID long, TYPE varchar(250), POI_NAME varchar(250), ST_NAME varchar(250), LAT number(31,15), LON number(31,15)
    -> Reprojector
T2019_KAR_STREET_NODE (reader SHAPEFILE_1)
    attributes: NODE_ID long, LINK_ID long, POINT_NUM long, Z_LEVEL long, INTERSECT varchar(1), LAT number(31,15), LON number(31,15)
    -> Reprojector
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> Reprojector
CSV (reader CSV2_2)
    attributes: col0 real32, col1 real32
    -> LineBuilder
LineBuilder
    ACCUM_INPUT_ATTRS_LOOKUP = One
    REMOVE_DUPLICATES_LOOKUP = NO
    ACCUM_INPUT_ATTRS = Use Attributes From One Feature
    REMOVE_DUPLICATES = No
    LINE -> Reprojector
Reprojector
    DEST = EPSG:3068
    INTERPOLATION_TYPE = NearestNeighbor
    RASTER_CELL_SIZE = PreserveCells
    RASTER_TOLERANCE = 0.0
    SOURCE = EPSG:4326
    REPROJECTED -> TestFilter
TestFilter
    DEFAULT_VALUE = <UNFILTERED>
    PASSED_TEST_GROUP_OUTPUT = FIRST
    TEST_LIST = "BOOL_OP,OR,COMPOSITE_TEST,""""""1"""""",TEST_CLAUSE,TEST @Value(fme_feature_type) = T2019_KAR_STREETS",@Value(fme_feature_type) = T2019_KAR_STREETS,"BOOL_OP,OR,COMPOSITE_TEST,""""""1"""""",TEST_CLAUSE,TEST @Value(fme_feature_type) = T2019_KAR_POI_TABLE",@Value(fme_feature_type) = T2019_KAR_POI_TABLE,"BOOL_OP,OR,COMPOSITE_TEST,""""""1"""""",TEST_CLAUSE,TEST @Value(fme_feature_type) = T2019_KAR_STREET_NODE",@Value(fme_feature_type) = T2019_KAR_STREET_NODE,"BOOL_OP,OR,COMPOSITE_TEST,""""""1"""""",TEST_CLAUSE,TEST @Value(fme_feature_type) = CSV",@Value(fme_feature_type) = CSV
    @Value(fme_feature_type) = T2019_KAR_STREETS -> ShortestPathFinder_2 [NETWORK]
    @Value(fme_feature_type) = T2019_KAR_POI_TABLE -> Clipper_2 [CANDIDATE]
    @Value(fme_feature_type) = T2019_KAR_STREET_NODE -> SpatialFilter [Candidate]
    @Value(fme_feature_type) = CSV -> ShortestPathFinder_2 [FROM-TO]
ShortestPathFinder_2
    ALLOW_UTURNS = Yes
    REORDER_MODE = NONE
    SNAP_POINTS = Yes
    SNAP_TOLERANCE = 200
    THREE_D = No
    WEIGHT_ATTR_CHOICE = BY_LENGTH
    PATH -> Bufferer_2
    PATH -> SpatialFilter [Filter]
    PATH -> LengthCalculator_2
Bufferer_2
    ANGLE = 22.5
    CAP_STYLE_LOOKUP = CAP_ARC
    CORNER_STYLE_LOOKUP = JOIN_ARC
    MODE = AREA
    OFFSET = 5
    OFFSET_UNITS = NONE
    PRECISION = APPROX
    CAP_STYLE = Arc
    CORNER_STYLE = Arc
    BUFFERED -> Clipper_2 [CLIPPER]
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> FeatureWriter [Inside]
FeatureWriter
    CONFIG_PARAMETERS = ESCAPE_COMMAS_IN_FTP_FORMAT_PARAMETERS,no
    DATASET = $(FME_MF_DIR_ENCODED)bez_kosztow.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    GEOJSON_WRITE_FEATURE_IDS = Yes
    GEOJSON_WRITE_NESTED = YES
    TOTAL_FEATURES_WRITTEN_ATTR = _total_features_written
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> bez_kosztow (writer GEODATABASE_FILE_2)
LengthCalculator_2
    DIM = 2
    LEN_ATTR = _length
    MULT = 1
    -> bez_kosztow (writer GEODATABASE_FILE_2)
bez_kosztow (writer GEODATABASE_FILE_2)
    attributes: col0 float, col1 float, POI_ID integer, LINK_ID integer, TYPE char(250), POI_NAME char(250), ST_NAME char(250), LAT double(31,15), LON double(31,15), NODE_ID integer, POINT_NUM integer, Z_LEVEL integer, INTERSECT char(1), REF_IN_ID integer, NREF_IN_ID integer, FUNC_CLASS char(1), SPEED_CAT char(1), FR_SPEED_L integer, TO_SPEED_L integer, DIR_TRAVEL char(1), _total_cost char(2048), _predicate char(2048), _length double
