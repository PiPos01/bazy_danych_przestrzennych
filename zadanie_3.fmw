FME workspace zadanie_3.fmw

Parameters:
- SourceDataset_OGCGEOPACKAGE = C:\Users\Piotr\Desktop\STUDIA\SEMESTR V\BAZY DANYCH PRZESTRZENNYCH\ćwiczenia\cwiczenia 9_10\bdline_gpkg_gb\Data\bdline_gb.gpkg   # GeoPackage File
- SourceDataset_TIFF = ""C:\Users\Piotr\Desktop\STUDIA\SEMESTR V\BAZY DANYCH PRZESTRZENNYCH\ćwiczenia\cwiczenia 9_10\ras250_gb\data\HP.tif" "C:\Users\Piotr\Desktop\STUDIA\SEMESTR V\BAZY DANYCH PRZESTRZENNYCH\ćwiczenia\cwiczenia 9_10\ras250_gb\data\HT.tif" "C:\Users\Piotr\Desktop\STUDIA\SEMESTR V\BAZY DANYCH PRZESTRZENNYCH\ćwiczenia\cwiczenia 9_10\ras250_gb\data\HU.tif" "C:\Users\Piotr\Desktop\STUDIA\SEMESTR V\BAZY DANYCH PRZESTRZENNYCH\ćwiczenia\cwiczenia 9_10\ras250_gb\data\HW.tif" "C:\Users\Piotr\Desktop\STUDIA\SEMESTR V\BAZY DANYCH PRZESTRZENNYCH\ćwiczenia\cwiczenia 9_10\ras250_gb\data\HX.tif" "C:\Users\Piotr\Desktop\STUDIA\SEMESTR V\BAZY DANYCH PRZESTRZENNYCH\ćwiczenia\cwiczenia 9_10\ras250_gb\data\HY.tif" "C:\Users\Piotr\Desktop\STUDIA\SEMESTR V\BAZY DANYCH PRZESTRZENNYCH\ćwiczenia\cwiczenia 9_10\ras250_gb\data\HZ.tif" "C:\Users\Piotr\Desktop\STUDIA\SEMESTR V\BAZY DANYCH PRZESTRZENNYCH\ćwiczenia\cwiczenia 9_10\ras250_gb\data\NA.tif" "C:\Users\Piotr\Desktop\STUDIA\SEMESTR V\BAZY DANYCH PRZESTRZENNYCH\ćwiczenia\cwiczenia 9_10\ras250_gb\data\NB.tif" "C:\Users\Piotr\Desktop\STUDIA\SEMESTR V\BAZY DANYCH PRZESTRZENNYCH\ćwiczenia\cwiczenia 9_10\ras250_gb\data\NC.tif" "C:\Users\Piotr\Desktop\STUDIA\SEMESTR V\BAZY DANYCH PRZESTRZENNYCH\ćwiczenia\cwiczenia 9_10\ras250_gb\data\ND.tif" "C:\Users\Piotr\Desktop\STUDIA\SEMESTR V\BAZY DANYCH PRZESTRZENNYCH\ćwiczenia\cwiczenia 9_10\ras250_gb\data\NF.tif" "C:\Users\Piotr\Desktop\STUDIA\SEMESTR V\BAZY DANYCH PRZESTRZENNYCH\ćwiczenia\cwiczenia 9_10\ras250_gb\data\NG.tif" "C:\Users\Piotr\Desktop\STUDIA\SEMESTR V\BAZY DANYCH PRZESTRZENNYCH\ćwiczenia\cwiczenia 9_10\ras250_gb\data\NH.tif" "C:\Users\Piotr\Desktop\STUDIA\SEMESTR V\BAZY DANYCH PRZESTRZENNYCH\ćwiczenia\cwiczenia 9_10\ras250_gb\data\NJ.tif" "C:\Users\Piotr\Desktop\STUDIA\SEMESTR V\BAZY DANYCH PRZESTRZENNYCH\ćwiczenia\cwiczenia 9_10\ras250_gb\data\NK.tif" "C:\Users\Piotr\Desktop\STUDIA\SEMESTR V\BAZY DANYCH PRZESTRZENNYCH\ćwiczenia\cwiczenia 9_10\ras250_gb\data\NL.tif" "C:\Users\Piotr\Desktop\STUDIA\SEMESTR V\BAZY DANYCH PRZESTRZENNYCH\ćwiczenia\cwiczenia 9_10\ras250_gb\data\NM.tif" "C:\Users\Piotr\Desktop\STUDIA\SEMESTR V\BAZY DANYCH PRZESTRZENNYCH\ćwiczenia\cwiczenia 9_10\ras250_gb\data\NN.tif" "C:\Users\Piotr\Desktop\STUDIA\SEMESTR V\BAZY DANYCH PRZESTRZENNYCH\ćwiczenia\cwiczenia 9_10\ras250_gb\data\NO.tif" "C:\Users\Piotr\Desktop\STUDIA\SEMESTR V\BAZY DANYCH PRZESTRZENNYCH\ćwiczenia\cwiczenia 9_10\ras250_gb\data\NR.tif" "C:\Users\Piotr\Desktop\STUDIA\SEMESTR V\BAZY DANYCH PRZESTRZENNYCH\ćwiczenia\cwiczenia 9_10\ras250_gb\data\NS.tif" "C:\Users\Piotr\Desktop\STUDIA\SEMESTR V\BAZY DANYCH PRZESTRZENNYCH\ćwiczenia\cwiczenia 9_10\ras250_gb\data\NT.tif" "C:\Users\Piotr\Desktop\STUDIA\SEMESTR V\BAZY DANYCH PRZESTRZENNYCH\ćwiczenia\cwiczenia 9_10\ras250_gb\data\NU.tif" "C:\Users\Piotr\Desktop\STUDIA\SEMESTR V\BAZY DANYCH PRZESTRZENNYCH\ćwiczenia\cwiczenia 9_10\ras250_gb\data\NW.tif" "C:\Users\Piotr\Desktop\STUDIA\SEMESTR V\BAZY DANYCH PRZESTRZENNYCH\ćwiczenia\cwiczenia 9_10\ras250_gb\data\NX.tif" "C:\Users\Piotr\Desktop\STUDIA\SEMESTR V\BAZY DANYCH PRZESTRZENNYCH\ćwiczenia\cwiczenia 9_10\ras250_gb\data\NY.tif" "C:\Users\Piotr\Desktop\STUDIA\SEMESTR V\BAZY DANYCH PRZESTRZENNYCH\ćwiczenia\cwiczenia 9_10\ras250_gb\data\NZ.tif" "C:\Users\Piotr\Desktop\STUDIA\SEMESTR V\BAZY DANYCH PRZESTRZENNYCH\ćwiczenia\cwiczenia 9_10\ras250_gb\data\OV.tif" "C:\Users\Piotr\Desktop\STUDIA\SEMESTR V\BAZY DANYCH PRZESTRZENNYCH\ćwiczenia\cwiczenia 9_10\ras250_gb\data\SC.tif" "C:\Users\Piotr\Desktop\STUDIA\SEMESTR V\BAZY DANYCH PRZESTRZENNYCH\ćwiczenia\cwiczenia 9_10\ras250_gb\data\SD.tif" "C:\Users\Piotr\Desktop\STUDIA\SEMESTR V\BAZY DANYCH PRZESTRZENNYCH\ćwiczenia\cwiczenia 9_10\ras250_gb\data\SE.tif" "C:\Users\Piotr\Desktop\STUDIA\SEMESTR V\BAZY DANYCH PRZESTRZENNYCH\ćwiczenia\cwiczenia 9_10\ras250_gb\data\SH.tif" "C:\Users\Piotr\Desktop\STUDIA\SEMESTR V\BAZY DANYCH PRZESTRZENNYCH\ćwiczenia\cwiczenia 9_10\ras250_gb\data\SJ.tif" "C:\Users\Piotr\Desktop\STUDIA\SEMESTR V\BAZY DANYCH PRZESTRZENNYCH\ćwiczenia\cwiczenia 9_10\ras250_gb\data\SK.tif" "C:\Users\Piotr\Desktop\STUDIA\SEMESTR V\BAZY DANYCH PRZESTRZENNYCH\ćwiczenia\cwiczenia 9_10\ras250_gb\data\SM.tif" "C:\Users\Piotr\Desktop\STUDIA\SEMESTR V\BAZY DANYCH PRZESTRZENNYCH\ćwiczenia\cwiczenia 9_10\ras250_gb\data\SN.tif" "C:\Users\Piotr\Desktop\STUDIA\SEMESTR V\BAZY DANYCH PRZESTRZENNYCH\ćwiczenia\cwiczenia 9_10\ras250_gb\data\SO.tif" "C:\Users\Piotr\Desktop\STUDIA\SEMESTR V\BAZY DANYCH PRZESTRZENNYCH\ćwiczenia\cwiczenia 9_10\ras250_gb\data\SP.tif" "C:\Users\Piotr\Desktop\STUDIA\SEMESTR V\BAZY DANYCH PRZESTRZENNYCH\ćwiczenia\cwiczenia 9_10\ras250_gb\data\SR.tif" "C:\Users\Piotr\Desktop\STUDIA\SEMESTR V\BAZY DANYCH PRZESTRZENNYCH\ćwiczenia\cwiczenia 9_10\ras250_gb\data\SS.tif" "C:\Users\Piotr\Desktop\STUDIA\SEMESTR V\BAZY DANYCH PRZESTRZENNYCH\ćwiczenia\cwiczenia 9_10\ras250_gb\data\ST.tif" "C:\Users\Piotr\Desktop\STUDIA\SEMESTR V\BAZY DANYCH PRZESTRZENNYCH\ćwiczenia\cwiczenia 9_10\ras250_gb\data\SU.tif" "C:\Users\Piotr\Desktop\STUDIA\SEMESTR V\BAZY DANYCH PRZESTRZENNYCH\ćwiczenia\cwiczenia 9_10\ras250_gb\data\SV.tif" "C:\Users\Piotr\Desktop\STUDIA\SEMESTR V\BAZY DANYCH PRZESTRZENNYCH\ćwiczenia\cwiczenia 9_10\ras250_gb\data\SW.tif" "C:\Users\Piotr\Desktop\STUDIA\SEMESTR V\BAZY DANYCH PRZESTRZENNYCH\ćwiczenia\cwiczenia 9_10\ras250_gb\data\SX.tif" "C:\Users\Piotr\Desktop\STUDIA\SEMESTR V\BAZY DANYCH PRZESTRZENNYCH\ćwiczenia\cwiczenia 9_10\ras250_gb\data\SY.tif" "C:\Users\Piotr\Desktop\STUDIA\SEMESTR V\BAZY DANYCH PRZESTRZENNYCH\ćwiczenia\cwiczenia 9_10\ras250_gb\data\SZ.tif" "C:\Users\Piotr\Desktop\STUDIA\SEMESTR V\BAZY DANYCH PRZESTRZENNYCH\ćwiczenia\cwiczenia 9_10\ras250_gb\data\TA.tif" "C:\Users\Piotr\Desktop\STUDIA\SEMESTR V\BAZY DANYCH PRZESTRZENNYCH\ćwiczenia\cwiczenia 9_10\ras250_gb\data\TF.tif" "C:\Users\Piotr\Desktop\STUDIA\SEMESTR V\BAZY DANYCH PRZESTRZENNYCH\ćwiczenia\cwiczenia 9_10\ras250_gb\data\TG.tif" "C:\Users\Piotr\Desktop\STUDIA\SEMESTR V\BAZY DANYCH PRZESTRZENNYCH\ćwiczenia\cwiczenia 9_10\ras250_gb\data\TL.tif" "C:\Users\Piotr\Desktop\STUDIA\SEMESTR V\BAZY DANYCH PRZESTRZENNYCH\ćwiczenia\cwiczenia 9_10\ras250_gb\data\TM.tif" "C:\Users\Piotr\Desktop\STUDIA\SEMESTR V\BAZY DANYCH PRZESTRZENNYCH\ćwiczenia\cwiczenia 9_10\ras250_gb\data\TQ.tif" "C:\Users\Piotr\Desktop\STUDIA\SEMESTR V\BAZY DANYCH PRZESTRZENNYCH\ćwiczenia\cwiczenia 9_10\ras250_gb\data\TR.tif" "C:\Users\Piotr\Desktop\STUDIA\SEMESTR V\BAZY DANYCH PRZESTRZENNYCH\ćwiczenia\cwiczenia 9_10\ras250_gb\data\TV.tif""   # Source TIFF (Tagged Image File Format) File(s)
- SourceDataset_GEOTIFF = ""C:\Users\Piotr\Desktop\STUDIA\SEMESTR V\BAZY DANYCH PRZESTRZENNYCH\ćwiczenia\cwiczenia 9_10\ras250_gb\data\HP.tif" "C:\Users\Piotr\Desktop\STUDIA\SEMESTR V\BAZY DANYCH PRZESTRZENNYCH\ćwiczenia\cwiczenia 9_10\ras250_gb\data\HT.tif" "C:\Users\Piotr\Desktop\STUDIA\SEMESTR V\BAZY DANYCH PRZESTRZENNYCH\ćwiczenia\cwiczenia 9_10\ras250_gb\data\HU.tif" "C:\Users\Piotr\Desktop\STUDIA\SEMESTR V\BAZY DANYCH PRZESTRZENNYCH\ćwiczenia\cwiczenia 9_10\ras250_gb\data\HW.tif" "C:\Users\Piotr\Desktop\STUDIA\SEMESTR V\BAZY DANYCH PRZESTRZENNYCH\ćwiczenia\cwiczenia 9_10\ras250_gb\data\HX.tif" "C:\Users\Piotr\Desktop\STUDIA\SEMESTR V\BAZY DANYCH PRZESTRZENNYCH\ćwiczenia\cwiczenia 9_10\ras250_gb\data\HY.tif" "C:\Users\Piotr\Desktop\STUDIA\SEMESTR V\BAZY DANYCH PRZESTRZENNYCH\ćwiczenia\cwiczenia 9_10\ras250_gb\data\HZ.tif" "C:\Users\Piotr\Desktop\STUDIA\SEMESTR V\BAZY DANYCH PRZESTRZENNYCH\ćwiczenia\cwiczenia 9_10\ras250_gb\data\NA.tif" "C:\Users\Piotr\Desktop\STUDIA\SEMESTR V\BAZY DANYCH PRZESTRZENNYCH\ćwiczenia\cwiczenia 9_10\ras250_gb\data\NB.tif" "C:\Users\Piotr\Desktop\STUDIA\SEMESTR V\BAZY DANYCH PRZESTRZENNYCH\ćwiczenia\cwiczenia 9_10\ras250_gb\data\NC.tif" "C:\Users\Piotr\Desktop\STUDIA\SEMESTR V\BAZY DANYCH PRZESTRZENNYCH\ćwiczenia\cwiczenia 9_10\ras250_gb\data\ND.tif" "C:\Users\Piotr\Desktop\STUDIA\SEMESTR V\BAZY DANYCH PRZESTRZENNYCH\ćwiczenia\cwiczenia 9_10\ras250_gb\data\NF.tif" "C:\Users\Piotr\Desktop\STUDIA\SEMESTR V\BAZY DANYCH PRZESTRZENNYCH\ćwiczenia\cwiczenia 9_10\ras250_gb\data\NG.tif" "C:\Users\Piotr\Desktop\STUDIA\SEMESTR V\BAZY DANYCH PRZESTRZENNYCH\ćwiczenia\cwiczenia 9_10\ras250_gb\data\NH.tif" "C:\Users\Piotr\Desktop\STUDIA\SEMESTR V\BAZY DANYCH PRZESTRZENNYCH\ćwiczenia\cwiczenia 9_10\ras250_gb\data\NJ.tif" "C:\Users\Piotr\Desktop\STUDIA\SEMESTR V\BAZY DANYCH PRZESTRZENNYCH\ćwiczenia\cwiczenia 9_10\ras250_gb\data\NK.tif" "C:\Users\Piotr\Desktop\STUDIA\SEMESTR V\BAZY DANYCH PRZESTRZENNYCH\ćwiczenia\cwiczenia 9_10\ras250_gb\data\NL.tif" "C:\Users\Piotr\Desktop\STUDIA\SEMESTR V\BAZY DANYCH PRZESTRZENNYCH\ćwiczenia\cwiczenia 9_10\ras250_gb\data\NM.tif" "C:\Users\Piotr\Desktop\STUDIA\SEMESTR V\BAZY DANYCH PRZESTRZENNYCH\ćwiczenia\cwiczenia 9_10\ras250_gb\data\NN.tif" "C:\Users\Piotr\Desktop\STUDIA\SEMESTR V\BAZY DANYCH PRZESTRZENNYCH\ćwiczenia\cwiczenia 9_10\ras250_gb\data\NO.tif" "C:\Users\Piotr\Desktop\STUDIA\SEMESTR V\BAZY DANYCH PRZESTRZENNYCH\ćwiczenia\cwiczenia 9_10\ras250_gb\data\NR.tif" "C:\Users\Piotr\Desktop\STUDIA\SEMESTR V\BAZY DANYCH PRZESTRZENNYCH\ćwiczenia\cwiczenia 9_10\ras250_gb\data\NS.tif" "C:\Users\Piotr\Desktop\STUDIA\SEMESTR V\BAZY DANYCH PRZESTRZENNYCH\ćwiczenia\cwiczenia 9_10\ras250_gb\data\NT.tif" "C:\Users\Piotr\Desktop\STUDIA\SEMESTR V\BAZY DANYCH PRZESTRZENNYCH\ćwiczenia\cwiczenia 9_10\ras250_gb\data\NU.tif" "C:\Users\Piotr\Desktop\STUDIA\SEMESTR V\BAZY DANYCH PRZESTRZENNYCH\ćwiczenia\cwiczenia 9_10\ras250_gb\data\NW.tif" "C:\Users\Piotr\Desktop\STUDIA\SEMESTR V\BAZY DANYCH PRZESTRZENNYCH\ćwiczenia\cwiczenia 9_10\ras250_gb\data\NX.tif" "C:\Users\Piotr\Desktop\STUDIA\SEMESTR V\BAZY DANYCH PRZESTRZENNYCH\ćwiczenia\cwiczenia 9_10\ras250_gb\data\NY.tif" "C:\Users\Piotr\Desktop\STUDIA\SEMESTR V\BAZY DANYCH PRZESTRZENNYCH\ćwiczenia\cwiczenia 9_10\ras250_gb\data\NZ.tif" "C:\Users\Piotr\Desktop\STUDIA\SEMESTR V\BAZY DANYCH PRZESTRZENNYCH\ćwiczenia\cwiczenia 9_10\ras250_gb\data\OV.tif" "C:\Users\Piotr\Desktop\STUDIA\SEMESTR V\BAZY DANYCH PRZESTRZENNYCH\ćwiczenia\cwiczenia 9_10\ras250_gb\data\SC.tif" "C:\Users\Piotr\Desktop\STUDIA\SEMESTR V\BAZY DANYCH PRZESTRZENNYCH\ćwiczenia\cwiczenia 9_10\ras250_gb\data\SD.tif" "C:\Users\Piotr\Desktop\STUDIA\SEMESTR V\BAZY DANYCH PRZESTRZENNYCH\ćwiczenia\cwiczenia 9_10\ras250_gb\data\SE.tif" "C:\Users\Piotr\Desktop\STUDIA\SEMESTR V\BAZY DANYCH PRZESTRZENNYCH\ćwiczenia\cwiczenia 9_10\ras250_gb\data\SH.tif" "C:\Users\Piotr\Desktop\STUDIA\SEMESTR V\BAZY DANYCH PRZESTRZENNYCH\ćwiczenia\cwiczenia 9_10\ras250_gb\data\SJ.tif" "C:\Users\Piotr\Desktop\STUDIA\SEMESTR V\BAZY DANYCH PRZESTRZENNYCH\ćwiczenia\cwiczenia 9_10\ras250_gb\data\SK.tif" "C:\Users\Piotr\Desktop\STUDIA\SEMESTR V\BAZY DANYCH PRZESTRZENNYCH\ćwiczenia\cwiczenia 9_10\ras250_gb\data\SM.tif" "C:\Users\Piotr\Desktop\STUDIA\SEMESTR V\BAZY DANYCH PRZESTRZENNYCH\ćwiczenia\cwiczenia 9_10\ras250_gb\data\SN.tif" "C:\Users\Piotr\Desktop\STUDIA\SEMESTR V\BAZY DANYCH PRZESTRZENNYCH\ćwiczenia\cwiczenia 9_10\ras250_gb\data\SO.tif" "C:\Users\Piotr\Desktop\STUDIA\SEMESTR V\BAZY DANYCH PRZESTRZENNYCH\ćwiczenia\cwiczenia 9_10\ras250_gb\data\SP.tif" "C:\Users\Piotr\Desktop\STUDIA\SEMESTR V\BAZY DANYCH PRZESTRZENNYCH\ćwiczenia\cwiczenia 9_10\ras250_gb\data\SR.tif" "C:\Users\Piotr\Desktop\STUDIA\SEMESTR V\BAZY DANYCH PRZESTRZENNYCH\ćwiczenia\cwiczenia 9_10\ras250_gb\data\SS.tif" "C:\Users\Piotr\Desktop\STUDIA\SEMESTR V\BAZY DANYCH PRZESTRZENNYCH\ćwiczenia\cwiczenia 9_10\ras250_gb\data\ST.tif" "C:\Users\Piotr\Desktop\STUDIA\SEMESTR V\BAZY DANYCH PRZESTRZENNYCH\ćwiczenia\cwiczenia 9_10\ras250_gb\data\SU.tif" "C:\Users\Piotr\Desktop\STUDIA\SEMESTR V\BAZY DANYCH PRZESTRZENNYCH\ćwiczenia\cwiczenia 9_10\ras250_gb\data\SV.tif" "C:\Users\Piotr\Desktop\STUDIA\SEMESTR V\BAZY DANYCH PRZESTRZENNYCH\ćwiczenia\cwiczenia 9_10\ras250_gb\data\SW.tif" "C:\Users\Piotr\Desktop\STUDIA\SEMESTR V\BAZY DANYCH PRZESTRZENNYCH\ćwiczenia\cwiczenia 9_10\ras250_gb\data\SX.tif" "C:\Users\Piotr\Desktop\STUDIA\SEMESTR V\BAZY DANYCH PRZESTRZENNYCH\ćwiczenia\cwiczenia 9_10\ras250_gb\data\SY.tif" "C:\Users\Piotr\Desktop\STUDIA\SEMESTR V\BAZY DANYCH PRZESTRZENNYCH\ćwiczenia\cwiczenia 9_10\ras250_gb\data\SZ.tif" "C:\Users\Piotr\Desktop\STUDIA\SEMESTR V\BAZY DANYCH PRZESTRZENNYCH\ćwiczenia\cwiczenia 9_10\ras250_gb\data\TA.tif" "C:\Users\Piotr\Desktop\STUDIA\SEMESTR V\BAZY DANYCH PRZESTRZENNYCH\ćwiczenia\cwiczenia 9_10\ras250_gb\data\TF.tif" "C:\Users\Piotr\Desktop\STUDIA\SEMESTR V\BAZY DANYCH PRZESTRZENNYCH\ćwiczenia\cwiczenia 9_10\ras250_gb\data\TG.tif" "C:\Users\Piotr\Desktop\STUDIA\SEMESTR V\BAZY DANYCH PRZESTRZENNYCH\ćwiczenia\cwiczenia 9_10\ras250_gb\data\TL.tif" "C:\Users\Piotr\Desktop\STUDIA\SEMESTR V\BAZY DANYCH PRZESTRZENNYCH\ćwiczenia\cwiczenia 9_10\ras250_gb\data\TM.tif" "C:\Users\Piotr\Desktop\STUDIA\SEMESTR V\BAZY DANYCH PRZESTRZENNYCH\ćwiczenia\cwiczenia 9_10\ras250_gb\data\TQ.tif" "C:\Users\Piotr\Desktop\STUDIA\SEMESTR V\BAZY DANYCH PRZESTRZENNYCH\ćwiczenia\cwiczenia 9_10\ras250_gb\data\TR.tif" "C:\Users\Piotr\Desktop\STUDIA\SEMESTR V\BAZY DANYCH PRZESTRZENNYCH\ćwiczenia\cwiczenia 9_10\ras250_gb\data\TV.tif""   # Source GeoTIFF File(s) or URL(s)
- DestDataset_POSTGIS = BDP_cw_9   # Connection
- DestDataset_POSTGIS_RASTER = BDP_9_FINAL   # Connection

Readers:
- OGCGEOPACKAGE_1: OGCGEOPACKAGE from $(SourceDataset_OGCGEOPACKAGE)
- TIFF_1: TIFF from $(SourceDataset_TIFF)
- GEOTIFF_1: GEOTIFF from $(SourceDataset_GEOTIFF)

Writers:
- POSTGIS_1: POSTGIS to $(DestDataset_POSTGIS)
- POSTGIS_RASTER_1: POSTGIS_RASTER to $(DestDataset_POSTGIS_RASTER)

scotland_and_wales_region (reader OGCGEOPACKAGE_1)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> Tester
Tester
    BOOL_OP = OR
    TEST_CLAUSE = CASE_INSENSITIVE_TEST @Value(File_Name) LIKE SOUTH_WALES%
    TEST_MODE = CASE_INSENSITIVE_TEST
    PASSED -> Clipper [CLIPPER]
    PASSED -> SpatialFilter [Filter]
GEOTIFF (reader GEOTIFF_1)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> RasterPaletteResolver
RasterPaletteResolver
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Exports (writer POSTGIS_RASTER_1)
Exports (writer POSTGIS_RASTER_1)
    attributes: name text, area_code text, area_description text, file_name text, feature_serial_number int4, collection_serial_number int4, global_polygon_id int4, admin_unit_id int4, census_code text, hectares float8, non_inland_area float8, area_type_code text, area_type_description text, non_area_type_code text, non_area_type_description text, _predicate varchar, _clipped char(3)
